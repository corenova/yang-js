module yang-store {
  prefix ys;
  namespace "urn:corenova:yang:store";
  yang-version 1.1;

  description
    "YANG store collects YANG modules and provides management operations";

  container store {
    config false;
    description "Main store which mounts all imported modules";
    notification update;
    notification create;
    notification delete;
  }
  
  container data {
    config false;
    description "Main dataroot which contains all imported module's properties";
  }

  rpc import {
    description
      "You can import additional models into the `yang-store` module to make
       them available for access/events/etc. It accepts
       [Model](./model.litcoffee), [Yang](./yang.litcoffee), YANG
       schema text, as well as arbitrary data object and will
       *aggregate* their properties under the `/ys:data` property.";
    
    output {
      leaf-list properties { type string; }
    }
  }

  rpc connect {
    description
      "The `Store` can establish data connection to data providers to
       load/synchronize data for the models imported into the `Store`.

       It accepts a URI string as `input` and operates similar to an
       ORM by loading appropriate `adapter` module based on the
       detected `protocol:`.";
  }

  notification connection;
}
