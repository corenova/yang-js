module yang-language {

  extension action           { argument name; }
  extension anydata          { argument name; }
  extension anyxml           { argument name; }
  extension augment          { argument target-node; }
  extension base             { argument name; }
  extension belongs-to       { argument module; }
  extension bit              { argument name; }
  extension case             { argument name; }
  extension choice           { argument condition; }
  extension config           { argument value; }
  extension contact          { argument text { yin-element true; } }
  extension container        { argument name; }
  extension default          { argument value; }
  extension description      { argument text { yin-element true; } } 
  extension deviate          { argument value; } // not-supprted, add, replace, delete
  extension deviation        { argument target-node; }
  extension enum             { argument name; }
  extension error-app-tag    { argument value; }
  extension error-message    { argument value { yin-element true; } }
  extension feature          { argument name; }
  extension fraction-digits  { argument value; }
  extension grouping         { argument name; }
  extension identity         { argument name; }
  extension if-feature       { argument name; }
  extension import           { argument module; }
  extension include          { argument module; }
  extension input            { }
  extension key              { argument value; }
  extension leaf             { argument name; }
  extension leaf-list        { argument name; }
  extension length           { argument value; }
  extension list             { argument name; }
  extension mandatory        { argument value; }
  extension max-elements     { argument value; }
  extension min-elements     { argument value; }
  extension modifier         { argument value; }
  extension module           { argument name; }
  extension must             { argument condition; }
  extension namespace        { argument uri; }
  extension notification     { argument event; }
  extension ordered-by       { argument value; }
  extension organization     { argument text { yin-element true; } }
  extension output           { }
  extension path             { argument value; }
  extension pattern          { argument value; }
  extension position         { argument value; }
  extension prefix           { argument value; }
  extension presence         { argument value; }
  extension range            { argument value; }
  extension reference        { argument text { yin-element true; } }
  extension refine           { argument target-node; }
  extension require-instance { argument value; }
  extension revision         { argument date; }
  extension revision-date    { argument date; }
  extension rpc              { argument name; }
  extension status           { argument value; } // current/deprecated/obsolete
  extension submodule        { argument name; }
  extension type             { argument name; }
  extension typedef          { argument name; }
  extension unique           { argument tag; }
  extension units            { argument value; }
  extension uses             { argument name; }
  extension value            { argument value; }
  extension when             { argument condition; }
  extension yang-version     { argument value; }
  extension yin-element      { argument value; }

  // built-in types
  typedef binary;
  typedef boolean;
  typedef decimal64;
  typedef empty;
  typedef enumeration;
  typedef identityref;
  typedef instance-identifier;
  typedef leafref;
  
  typedef integer {
    description "A generic integer type (non rfc6020)";
  }
  // following are defined as derived 'number' type with range restrictions
  typedef int8   { type integer { range -128..127; } }
  typedef int16  { type integer { range -32768..32767; } }
  typedef int32  { type integer { range -2147483648..2147483647; } } 
  typedef int64  { type integer { range -9223372036854775808..9223372036854775807; } }
  typedef uint8  { type integer { range 0..255; } }
  typedef uint16 { type integer { range 0..65535; } }
  typedef uint32 { type integer { range 0..4294967295; } }
  typedef uint64 { type integer { range 0..18446744073709551615; } }
  
  typedef string;
  typedef union;

  // these declarations are required for YANG 1.1
  namespace "urn:corenova:lang";
  prefix lang;
  yang-version 1.1;
}
